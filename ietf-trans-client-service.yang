module ietf-trans-client-service {
  yang-version 1.1;
  namespace
    "urn:ietf:params:xml:ns:yang:ietf-trans-client-service";
  prefix clnt-svc;

  import ietf-yang-types {
    prefix yang;
    reference "RFC 6991: Common YANG Data Types";
  }

  import ietf-te-types {
    prefix te-types;
    reference "RFCYYYY: Traffic Engineering Common YANG Types";
  }
  // RFC Editor: replace YYYY with the actual RFC number assigned
  // to the RFC once draft-ietf-teas-rfc8776-update
  // becomes an RFC, update date information and remove this note.

  import ietf-layer1-types {
    prefix l1-types;
    reference "RFCZZZZ: A YANG Data Model for Layer 1 Types";
  }
  // RFC Editor: replace ZZZZ with the actual RFC number assigned
  // to the RFC once draft-ietf-ccamp-layer1-types
  // becomes an RFC, update date information and remove this note.

  import ietf-network {
    prefix nw;
    reference "RFC8345: A YANG Data Model for Network Topologies";
  }

  import ietf-network-topology {
    prefix nt;
    reference "RFC8345: A YANG Data Model for Network Topologies";
  }

  import ietf-trans-client-svc-types {
    prefix clnt-types;
    reference
      "RFCXXXX: A YANG Data Model for Transport Network Client 
      Signals";
  }
  // RFC Editor: replace XXXX with the actual RFC number assigned
  // to the RFC once this draft
  // becomes an RFC, update date information and remove this note.

  organization
    "Internet Engineering Task Force (IETF) CCAMP WG";
  contact
    "WG Web: <https://datatracker.ietf.org/wg/ccamp/>
     WG List: <mailto:ccamp@ietf.org>

     Editor: Haomian Zheng
             <mailto:zhenghaomian@huawei.com>

     Editor: Aihua Guo
             <mailto:aihuaguo.ietf@gmail.com>

     Editor: Italo Busi
             <mailto:italo.busi@huawei.com>

     Editor: Anton Snitser
             <mailto:asnizar@cisco.com>

     Editor: Francesco Lazzeri
             <mailto:francesco.lazzeri@ericsson.com>

     Editor: Chaode Yu
             <mailto:yuchaode@huawei.com>";

  description
    "This module defines a YANG data model for describing
    transport network client services.

    The model fully conforms to the Network Management
    Datastore Architecture (NMDA).

    Copyright (c) 2024 IETF Trust and the persons
    identified as authors of the code.  All rights reserved.

    Redistribution and use in source and binary forms, with or
    without modification, is permitted pursuant to, and subject
    to the license terms contained in, the Revised BSD License
    set forth in Section 4.c of the IETF Trust's Legal Provisions
    Relating to IETF Documents
    (https://trustee.ietf.org/license-info).

    This version of this YANG module is part of RFC XXXX; see
    the RFC itself for full legal notices.";

  revision 2024-01-11 {
    description
      "Initial Version";
    reference
      "RFC XXXX: A YANG Data Model for Transport Network Client
      Signals";
  }
  // RFC Editor: replace XXXX with the actual RFC number assigned
  // to the RFC once this draft
  // becomes an RFC, update date information and remove this note.

  /*
   * Groupings
   */

  grouping client-svc-access-parameters {
    description
      "Transport network client signals access parameters";

    leaf access-node-id {
      type te-types:te-node-id;
      description
        "The identifier of the access node in the TE topology.";
    }
    leaf access-node-uri {
      type nw:node-id;
      description
        "The identifier of the access node in the network.";
    }
    leaf access-ltp-id {
      type te-types:te-tp-id;
      description
        "The TE link termination point identifier in TE topology, 
        used together with access-node-id to identify the access
        Link Termination Point (LTP).";
    }
    leaf access-ltp-uri {
      type nt:tp-id;
      description
        "The link termination point identifier in network topology,
        used together with access-node-uri to identify the access
        LTP";
    }
    leaf client-signal {
      type identityref {
        base l1-types:client-signal;
      }
      description
        "Identify the client signal type associated with this port";
    }
  }

  grouping pm-state-grouping {
    description
      "Performance Monitoring (PM) state attributes";
    leaf latency {
      type uint32;
      units microsecond;
      description
        "latency value of the E2E client signal service";
    }
  }

  grouping error-info-grouping {
    description
      "Error information parameters";
    leaf error-code {
      type uint16;
      description "error code";
    }
    leaf error-description {
      type string;
      description "detail message of error";
    }
    leaf error-timestamp {
      type yang:date-and-time;
      description "the date and time error is happened";
    }
  }

  grouping alarm-threshold-grouping {
    description
      "Alarm threshold parameters.";
    leaf latency-threshold {
      type uint32;
      units microsecond;
      description
        "a threshold for the E2E client signal service's
        latency. Once the latency value exceed this threshold,
        an alarm should be triggered.";
    }
  }

  grouping client-svc-tunnel-parameters {
    description
      "Transport network client signals tunnel parameters";

    leaf tunnel-name {
      type string;
      description
        "TE tunnel instance name.";
    }
  }

  grouping  client-svc-instance-config {
    description
      "Configuration parameters for client services.";

    leaf client-svc-name {
      type string;
      description
        "Identifier of the p2p transport network client signals.";
    }
    leaf client-svc-title {
      type string;
      description
        "Name of the p2p transport network client signals.";
    }
    leaf user-label {
      type string;
      description
        "Alias of the p2p transport network client signals.";
    }
    leaf client-svc-descr {
      type string;
      description
        "Description of the transport network client signals.";
    }
    leaf client-svc-customer {
      type string;
      description
        "Customer of the transport network client signals.";
    }
    container resilience {
      description "Place holder for resilience functionalities";
    }
    uses te-types:te-topology-identifier;
    leaf admin-status {
      type identityref {
        base te-types:tunnel-admin-state-type;
      }
      default te-types:tunnel-admin-state-up;
      description "Client signals administrative state.";
    }
    container src-access-ports {
      description
        "Source access port of a client signal.";
      uses client-svc-access-parameters;
    }
    container dst-access-ports {
      description
        "Destination access port of a client signal.";
      uses client-svc-access-parameters;
    }
    container pm-state {
      config false;
      description "PM data of E2E client signal";
      uses pm-state-grouping;
    }
    container error-info {
      config false;
      description "error messages of configuration";
      uses error-info-grouping;
    }
    container alarm-threshold {
      description
        "threshold configuration for the E2E client signal";
      uses alarm-threshold-grouping;
    }
    leaf direction {
      type identityref {
        base clnt-types:direction;
      }
      description "Uni-dir or Bi-dir for the client signal.";
    }
    list svc-tunnels {
      key tunnel-name;
      description
        "List of the TE Tunnels supporting the client signal.";
      uses client-svc-tunnel-parameters;
    }
  }

  grouping  client-svc-instance-state {
    description
      "State parameters for client services.";
    leaf operational-state {
      type identityref {
        base te-types:tunnel-state-type;
      }
      config false;
      description "Client signal operational state.";
    }
    leaf provisioning-state {
      type identityref {
        base te-types:lsp-state-type;
      }
      config false;
      description "Client signal provisioning state.";
    }
    leaf creation-time {
      type yang:date-and-time;
      config false;
      description "The time of the client signal be created.";
    }
    leaf last-updated-time {
      type yang:date-and-time;
      config false;
      description "The time of the client signal's latest update.";
    }
    leaf created-by {
      type string;
      config false;
      description
        "The client signal is created by whom,
        can be a system or staff ID.";
    }
    leaf last-updated-by {
      type string;
      config false;
      description
        "The client signal is last updated by whom,
        can be a system or staff ID.";
    }
    leaf owned-by {
      type string;
      config false;
      description
        "The client signal is owned by whom,
        can be a system ID.";
    }
  }

  /*
   * Data nodes
   */

  container client-svc {
    description
      "Transport client services.";

    list client-svc-instances {
      key client-svc-name;
      description
        "The list of p2p transport client service instances";
      uses client-svc-instance-config;
      uses client-svc-instance-state;
    }
  }
}

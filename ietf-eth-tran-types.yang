module ietf-eth-tran-types {
  yang-version 1.1;
  namespace "urn:ietf:params:xml:ns:yang:ietf-eth-tran-types";
  prefix etht-types;

  organization
    "Internet Engineering Task Force (IETF) CCAMP WG";
  contact
    "WG Web: <https://datatracker.ietf.org/wg/ccamp/>
     WG List: <mailto:ccamp@ietf.org>

     Editor: Haomian Zheng
             <mailto:zhenghaomian@huawei.com>

     Editor: Aihua Guo
             <mailto:aihuaguo.ietf@gmail.com>

     Editor: Italo Busi
             <mailto:italo.busi@huawei.com>

     Editor: Anton Snitser
             <mailto:asnizar@cisco.com>

     Editor: Francesco Lazzeri
             <mailto:francesco.lazzeri@ericsson.com>

     Editor: Chaode Yu
             <mailto:yuchaode@huawei.com>";

  description
    "This module defines a collection of common YANG identity, data
    type and grouping definitions for describing Ethernet transport
    network clients.

    Copyright (c) 2024 IETF Trust and the persons
    identified as authors of the code.  All rights reserved.

    Redistribution and use in source and binary forms, with or
    without modification, is permitted pursuant to, and subject
    to the license terms contained in, the Revised BSD License
    set forth in Section 4.c of the IETF Trust's Legal Provisions
    Relating to IETF Documents
    (https://trustee.ietf.org/license-info).

    This version of this YANG module is part of RFC XXXX; see
    the RFC itself for full legal notices.";

  revision 2024-01-11 {
    description
      "Initial Version";
    reference
      "RFC XXXX: A YANG Data Model for Transport Network Client
      Signals";
  }
  // RFC Editor: replace XXXX with the actual RFC number assigned
  // to the RFC once this draft
  // becomes an RFC, update date information and remove this note.

  /*
   * Identities
   */

  identity eth-vlan-tag-type {
    description
      "ETH VLAN tag type.";
  }

    identity c-vlan-tag-type {
      base eth-vlan-tag-type;
      description
        "802.1Q Customer VLAN";
    }

    identity s-vlan-tag-type {
      base eth-vlan-tag-type;
      description
        "802.1Q Service VLAN (QinQ)";
    }

  identity service-classification-type {
    description
      "Service classification.";
  }

    identity port-classification {
      base service-classification-type;
      description
        "Port classification.";
    }

    identity vlan-classification {
      base service-classification-type;
      description
        "VLAN classification.";
    }

    identity eth-vlan-tag-classify {
      description
        "VLAN tag classification.";
    }

      identity classify-c-vlan {
        base eth-vlan-tag-classify;
        description
          "Classify 802.1Q Customer VLAN tag.
          Only C-tag type is accepted";
      }

      identity classify-s-vlan {
        base eth-vlan-tag-classify;
        description
          "Classify 802.1Q Service VLAN (QinQ) tag.
          Only S-tag type is accepted";
      }

      identity classify-s-or-c-vlan {
        base eth-vlan-tag-classify;
        description
          "Classify S-VLAN or C-VLAN tag-classify.
          Either tag is accepted";
      }

  identity bandwidth-profile-type {
    description
      "Bandwidth Profile Types";
  }

    identity mef-10-bwp {
      base bandwidth-profile-type;
      description
        "MEF 10 Bandwidth Profile";
    }

    identity rfc-2697-bwp {
      base bandwidth-profile-type;
      description
        "RFC 2697 Bandwidth Profile";
    }

    identity rfc-2698-bwp {
      base bandwidth-profile-type;
      description
        "RFC 2698 Bandwidth Profile";
    }

    identity rfc-4115-bwp {
      base bandwidth-profile-type;
      description
        "RFC 4115 Bandwidth Profile";
    }

  identity service-type {
    description
      "Type of Ethernet service.";
  }

    identity p2p-svc {
      base service-type;
      description
        "Ethernet point-to-point service (EPL, EVPL).";
    }

    identity rmp-svc {
      base service-type;
      description
        "Ethernet rooted-multitpoint service (E-TREE, EP-TREE).";
    }

    identity mp2mp-svc {
      base service-type;
      description
        "Ethernet multipoint-to-multitpoint service
        (E-LAN, EP-LAN).";
    }

  identity lifecycle-status {
    description
      "Lifecycle Status.";
  }

    identity installed {
      base lifecycle-status;
      description
        "Installed.";
    }

    identity planned {
      base lifecycle-status;
      description
        "Planned.";
    }

    identity pending-removal {
      base lifecycle-status;
      description
        "Pending Removal.";
    }

  identity topology-role {
    description
      "The role of underlay topology: e.g., hub, spoke,
      any-to-any.";
  }

  identity resilience {
    description
    "Placeholder for resilience information in data plane,
    for future study. ";
  }

  identity access-role {
    description
    "Indicating whether the access is a working or protection
    access.";
  }

    identity root-primary {
      base access-role;
      description
        "Designates the primary root UNI of an E-Tree service, and 
        may also designates the UNI access role of E-LINE and E-LAN
        service.";
    }

    identity root-backup {
      base access-role;
      description
        "Designates the backup root UNI of an E-Tree service.";
    }

    identity leaf-access {
      base access-role;
      description
        "Designates the leaf UNI of an E-Tree service.";
    }

  identity performance {
    description
    "Placeholder for performance information, for future study.";
  }

  identity encapsulation-type {
    description
    "Indicating how the service is encapsulated (to PW), e.g, raw or
    tag. ";
  }

  /*
   * Data Types
   */

  typedef eth-tag-type {
    type identityref {
      base eth-vlan-tag-type;
    }
    description
      "Identifies a specific ETH VLAN tag type.";
  }

  typedef eth-tag-classify {
    type identityref {
      base eth-vlan-tag-classify;
    }
    description
      "Identifies a specific VLAN tag classification.";
  }

  typedef vlanid {
    type uint16 {
      range "1..4094";
    }
    description
      "The 12-bit VLAN-ID used in the VLAN Tag header.";
  }

  typedef vid-range-type {
    type string {
      pattern "([1-9][0-9]{0,3}(-[1-9][0-9]{0,3})?" +
              "(,[1-9][0-9]{0,3}(-[1-9][0-9]{0,3})?)*)";
    }
    description
      "A list of VLAN Ids, or non overlapping VLAN ranges, in
       ascending order, between 1 and 4094.
       This type is used to match an ordered list of VLAN Ids, or
       contiguous ranges of VLAN Ids. Valid VLAN Ids must be in the
       range 1 to 4094, and included in the list in non overlapping
       ascending order.

       For example: 1,10-100,50,500-1000";
  }

  typedef bandwidth-profile-type {
    type identityref {
      base bandwidth-profile-type;
    }
    description
      "Identifies a specific Bandwidth Profile type.";
  }

  typedef service-type {
    type identityref {
      base service-type;
    }
    description
      "Identifies the type of Ethernet service.";
  }

  typedef lifecycle-status {
    type identityref {
      base lifecycle-status;
    }
    description
      "Identifies the lLifecycle Status .";
  }

  /*
   * Groupings
   */

  grouping etht-bandwidth-profiles {
    description
      "Bandwidth profile configuration paramters.";

    leaf bandwidth-profile-type {
      type etht-types:bandwidth-profile-type;
      description
        "The type of bandwidth profile.";
    }
    leaf CIR {
      type uint64;
      description
        "Committed Information Rate in Kbps";
    }
    leaf CBS {
      type uint64;
      description
        "Committed Burst Size in in KBytes";
    }
    leaf EIR {
      type uint64;
      /* Need to indicate that EIR is not supported by RFC 2697

      must
        '../bw-profile-type = "mef-10-bwp" or ' +
        '../bw-profile-type = "rfc-2698-bwp" or ' +
        '../bw-profile-type = "rfc-4115-bwp"'

      must
        '../bw-profile-type != "rfc-2697-bwp"'
      */
      description
        "Excess Information Rate in Kbps
         In case of RFC 2698, PIR = CIR + EIR";
    }
    leaf EBS {
      type uint64;
      description
        "Excess Burst Size in KBytes.
          In case of RFC 2698, PBS = CBS + EBS";
    }
    leaf color-aware {
      type boolean;
      description
        "Indicates weather the color-mode is
        color-aware or color-blind.";
    }
    leaf coupling-flag {
      type boolean;
      /* Need to indicate that Coupling Flag is defined only for
         MEF 10

      must
        '../bw-profile-type = "mef-10-bwp"'
      */
      description
        "Coupling Flag.";
    }
  }

  grouping pw-segement-bandwidth-profile-grouping {
    description
      "bandwidth profile grouping for PW segment.";

    leaf bandwidth-profile-type {
      type etht-types:bandwidth-profile-type;
      description
        "The type of bandwidth profile.";
    }
    leaf CIR {
      type uint64;
      description
        "Committed Information Rate in Kbps";
    }
    leaf CBS {
      type uint64;
      description
        "Committed Burst Size in in KBytes";
    }
    leaf EIR {
      type uint64;
      /* Need to indicate that EIR is not supported by RFC 2697

      must
        '../bw-profile-type = "mef-10-bwp" or ' +
        '../bw-profile-type = "rfc-2698-bwp" or ' +
        '../bw-profile-type = "rfc-4115-bwp"'

      must
        '../bw-profile-type != "rfc-2697-bwp"'
      */
      description
        "Excess Information Rate in Kbps
         In case of RFC 2698, PIR = CIR + EIR";
    }
    leaf EBS {
      type uint64;
      description
        "Excess Burst Size in KBytes.
          In case of RFC 2698, PBS = CBS + EBS";
    }
  }

  grouping eth-bandwidth {
    description
      "Available bandwith for ethernet.";
    leaf eth-bandwidth {
      type uint64{
        range "0..10000000000";
      }
      units "Kbps";
      description
        "Available bandwith value expressed in kilobits per second";
    }
  }

  grouping eth-label-restriction {
    description
      "Label Restriction for ethernet.";
    leaf tag-type {
      type etht-types:eth-tag-type;
      description "VLAN tag type.";
    }
    leaf priority {
      type uint8;
      description "priority.";
    }
  }

  grouping eth-label {
    description
      "Label for ethernet.";
    leaf vlanid {
      type etht-types:vlanid;
        description
          "VLAN tag id.";
    }
  }

  grouping eth-label-step {
    description "Label step for Ethernet VLAN";
    leaf eth-step {
      type uint16 {
        range "1..4095";
      }
      default 1;
      description
        "Label step which represent possible increments for
        an Ethernet VLAN tag.";
      reference
        "IEEE 802.1ad: Provider Bridges.";
    }
  }
}
